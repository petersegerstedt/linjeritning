FME workspace juni.dxf2juni3D.dwg.fmw

Parameters:
- SourceDataset_ACAD = $(FME_MF_DIR)juni.dxf   # Source Autodesk AutoCAD DWG/DXF File(s)
- FEATURE_TYPES =

Readers:
- ACAD_1: ACAD from $(SourceDataset_ACAD)

0 (reader ACAD_1)
    -> GeometryFilter
Note: +--------------------+ +---------------+ / | view1 - SB to BB | | view4: Frames | / | | | | / | | | | / | | | | / +--------------------+ +---------------+ / +--------------------+ / | view2 - Waterlines | / | | / +--------------------+ / +--------------------+ / | view3 - Diagonals | / | | / +--------------------+
GeometryFilter
    BREAK_AGG = No
    GEOM_PORT_NAMES = Point Line Raster
    POINT -> Junction
    LINE -> Junction
    LINE -> TestFilter
    <UNFILTERED> -> Logger_UnexpectedGeometry
Logger_UnexpectedGeometry
    LOG_FEATURE = LOG_ONLY
    MAXCOORDS = 20
    MAXFEATS = 20
    MESSAGE = Feature is:
    SEVERITY = INFO
Note: Next up: / - Intersect diagonals with frames and get frame fit points - done / - move fit points to frames view (view4)
Junction
    -> PythonCaller
PythonCaller
    NEW_ATTRIBUTES = model
    PYTHONSOURCE:
      import fmeobjects
      import json
      import sys
      sys.path.append('NURBS-Python')
      from geomdl import BSpline
      from geomdl import knotvector
      import math

      '''
       +--------------------+  +---------------+
       | view1 - SB to BB   |  | view4: Frames |
       |                    |  |               |
       |                    |  |               |
       |                    |  |               |
       +--------------------+  +---------------+
       +--------------------+
       | view2 - Waterlines |
       |                    |
       +--------------------+
       +--------------------+
       | view3 - Diagonals  |
       |                    |
       +--------------------+
      '''
      class FeatureProcessor(object):
          def __init__(self):
              self.model = {'fit_points':[]}
          def input(self,feature):
              if 'autocad_spline' == feature.getAttribute('autocad_entity'):
                  return self.input_spline(feature)
              elif 'autocad_line' == feature.getAttribute('autocad_entity'):
                  return self.input_line(feature)
              elif 'autocad_point' == feature.getAttribute('autocad_entity'):
                  return self.input_point(feature)
              #self.pyoutput(feature)
          def input_point(self, feature):
              ftype = feature.getAttribute('fme_feature_type')
              x,y,_ = feature.getGeometry().getXYZ()
              if ftype in ('view1_origo', 'view2_origo', 'view3_origo', 'view4_origo'):
                  self.model[ftype] = (x,y)
              elif 'diagonal_fit_point' == ftype:
                  frame = feature.getAttribute('frame')
                  diagonal = feature.getAttribute('diagonal')
                  view = feature.getAttribute('view')
                  self.model['fit_points'].append({'kind':'diagonal','frame': frame, 'pt': [x,y], 'diagonal':diagonal, 'view': view})
              elif 'deckline_fit_point' == ftype:
                  frame = feature.getAttribute('frame')
                  view = feature.getAttribute('view')
                  self.model['fit_points'].append({'kind':'deckline','frame': frame, 'pt': [x,y], 'view': view})
          def input_line(self, feature):
              ftype = feature.getAttribute('fme_feature_type')
              x1,y1,_ = feature.getGeometry().bounds()[0].getXYZ()
              x2,y2,_ = feature.getGeometry().bounds()[1].getXYZ()
              if ftype in ('view1_kvl', 'view2_center', 'view3_center', 'view4_kvl'):
                  self.model[ftype] = y1
              elif ftype in ('s1', 's2', 's3', 's4', 's5' 's6', 's7', 'view4_center'):
                  self.model[ftype] = x1
              elif ftype in ('d1', 'd2', 'd3', 'd4'):
                  if not 'diagonal_planes' in self.model:
                      self.model['diagonal_planes'] = {'d1':{},'d2':{},'d3':{},'d4':{}}
                  self.model['diagonal_planes'][ftype] = (y2, math.atan2(y2-y1, x2-x1))
          def input_spline(self, feature):
              model_part = feature.getAttribute('fme_feature_type')
              ctrl_x, ctrl_y = [feature.getAttribute('autocad_control_{}'.format(s)) for s in ['x','y']]
              ctrlpts = [[float(x),float(y)] for (x,y) in zip(*[s.split(',') for s in [ctrl_x, ctrl_y]])]
              self.model[model_part] = ctrlpts

          def build_deckline(self):
              feature = fmeobjects.FMEFeature()
              offset_x, offset_y = self.model['view2_origo']
              deck_line = [[x1 - offset_x, y2 - offset_y, y1 - self.model['view1_kvl']] for (x1,y1),(x2,y2) in zip(self.model['dl_sb_to_bb'], self.model['dl_top_down'])]
              self.model['derived'] = {'deck_line': deck_line}
              curve = BSpline.Curve()
              curve.degree = 2
              # Set control points
              curve.ctrlpts = deck_line
              curve.knotvector = knotvector.generate(curve.degree, curve.ctrlpts_size)
              points = [(x,y,z) for (x,y,z) in curve.evalpts]
              geom = fmeobjects.FMELine(points)
              feature.setGeometry(geom)
              feature.setAttribute('ctrlpts.json', json.dumps(deck_line))
              feature.setAttribute('autocad_control_x', ','.join([str(x) for x, y, z in deck_line]))
              feature.setAttribute('autocad_control_y', ','.join([str(y) for x, y, z in deck_line]))
              feature.setAttribute('autocad_control_z', ','.join([str(z) for x, y, z in deck_line]))
              feature.setAttribute('fme_feature_type', 'deck_line')
              feature.setAttribute('autocad_entity','autocad_spline')
              return(feature)

          def build_diagonals(self):
              for diagonal in ['d1','d2','d3','d4']:
                  feature = fmeobjects.FMEFeature()
                  height_in_view4, angle = self.model['diagonal_planes'][diagonal]
                  z0 = height_in_view4 - self.model['view4_origo'][1]
                  offset_x, offset_y = self.model['view3_origo']
                  ctrl_pts = [(x - offset_x, y - offset_y, z0) for x,y in self.model[diagonal]]
                  feature.setGeometry(fmeobjects.FMELine(ctrl_pts))
                  feature.setAttribute('z0', z0)
                  feature.setAttribute('angle', angle)
                  feature.setAttribute('fme_feature_type', diagonal)
                  yield feature
                  #deck_line = [[x1, y2 - self.model['view2_center'], y1 - self.model['view1_kvl']] for (x1,y1),(x2,y2) in zip(self.model['dl_sb_to_bb'], self.model['dl_top_down'])]
          def build_sections(self):
              deckline = {}
              for pt in self.model['fit_points']:
                  '''
                  {
                      "frame": "s2",
                      "kind": "deckline",
                      "pt": [
                          173.8740216871854,
                          233.27641186396372
                      ],
                      "view": "3"
                  }
                  '''
                  offset_x, offset_y = self.model['view{}_origo'.format(pt['view'])]
                  x = pt['pt'][0] - offset_x
                  y = pt['pt'][1] - offset_y
                  if 'diagonal' == pt['kind']:
                      height_in_view4, angle = self.model['diagonal_planes'][pt['diagonal']]
                      z0 = height_in_view4 - self.model['view4_origo'][1]
                      feature = fmeobjects.FMEFeature()
                      feature.setGeometry(fmeobjects.FMEPoint(x,y,z0))
                      feature.setAttribute('frame', pt['frame'])
                      feature.setAttribute('kind', pt['kind'])
                      feature.setAttribute('view', pt['view'])
                      feature.setAttribute('z0', z0)
                      feature.setAttribute('angle', angle)
                      feature.setAttribute('diagonal', pt['diagonal'])
                      feature.setAttribute('fme_feature_type', 'fit_point')
                      yield feature
                  elif 'deckline' == pt['kind']:
                      frame = pt['frame']
                      view = int(pt['view'])
                      if not frame in deckline:
                          deckline[frame] = (x,y)
                      elif 1 == view:
                          z = y
                          x,y = deckline[frame]
                          feature = fmeobjects.FMEFeature()
                          feature.setGeometry(fmeobjects.FMEPoint(x,y,z))
                          feature.setAttribute('frame', pt['frame'])
                          feature.setAttribute('kind', pt['kind'])
                          feature.setAttribute('view', pt['view'])
                          feature.setAttribute('fme_feature_type', 'fit_point')
                          yield feature
                      elif 2 == view:
                          _,z = deckline[frame]
                          feature = fmeobjects.FMEFeature()
                          feature.setGeometry(fmeobjects.FMEPoint(x,y,z))
                          feature.setAttribute('frame', pt['frame'])
                          feature.setAttribute('kind', pt['kind'])
                          feature.setAttribute('view', pt['view'])
                          feature.setAttribute('fme_feature_type', 'fit_point')
                          yield feature


          def close(self):
              self.pyoutput(self.build_deckline())
              for feature in self.build_diagonals():
                  self.pyoutput(feature)
              for feature in self.build_sections():
                  self.pyoutput(feature)

              model_feature = fmeobjects.FMEFeature()
              model_feature.setAttribute('fme_feature_type', 'model')
              model_feature.setAttribute('model', json.dumps(self.model, sort_keys=True, indent=4))
              self.pyoutput(model_feature)
    PYTHONSYMBOL = FeatureProcessor
    -> AttributeFilter
AttributeFilter
    ATTR_NAME = fme_feature_type
    ATTR_VALUES = d1,d2,d3,d4,deck_line,model,<Empty>,<Missing>,<Null>,<Unfiltered>,fit_point
    d1 -> Junction_4
    d2 -> Junction_4
    d3 -> Junction_4
    d4 -> Junction_4
    deck_line -> Junction_3
    model -> AttributeFilter_model
    <UNFILTERED> -> AttributeFilter__Unfiltered_
    fit_point -> AttributeExposer_2
Junction_4
    -> AttributeExposer
AttributeExposer
    ATTR_LIST = angle,z0
    -> 3DRotator
3DRotator
    ANGLE = -@radToDeg(@Value(angle))
    AXIS_CHOICE = Custom Axis
    XDIR = 1
    XORIG = 0
    YDIR = 0
    YORIG = 0
    ZDIR = 0
    ZORIG = @Value(z0)
    ROTATED -> PythonCaller_2
PythonCaller_2
    NEW_ATTRIBUTES = ctrlpts.json autocad_control_x autocad_control_y autocad_control_z autocad_entity
    PYTHONSOURCE:
      import fmeobjects
      import sys
      sys.path.append('NURBS-Python')
      from geomdl import BSpline
      from geomdl import knotvector
      import json
      class FeatureProcessor(object):
          def __init__(self):
              pass
          def input(self,feature):
              curve = BSpline.Curve()
              curve.degree = 2
              # Set control points
              curve.ctrlpts = [point.getXYZ() for point in feature.getGeometry().getPoints()]
              curve.knotvector = knotvector.generate(curve.degree, curve.ctrlpts_size)
              points = [(x,y,z) for (x,y,z) in curve.evalpts]
              geom = fmeobjects.FMELine(points)
              feature.setGeometry(geom)
              feature.setAttribute('ctrlpts.json', json.dumps(curve.ctrlpts))
              feature.setAttribute('autocad_control_x', ','.join([str(x) for x, y, z in curve.ctrlpts]))
              feature.setAttribute('autocad_control_y', ','.join([str(y) for x, y, z in curve.ctrlpts]))
              feature.setAttribute('autocad_control_z', ','.join([str(z) for x, y, z in curve.ctrlpts]))
              feature.setAttribute('autocad_entity','autocad_spline')
              self.pyoutput(feature)
          def close(self):
              pass
    PYTHONSYMBOL = FeatureProcessor
    -> Junction_5
    -> AttributeCreator_9
    -> diagonal
    -> Scaler_2
diagonal: Inspector
AttributeCreator_9
    ATTR_TABLE = SET_TO _order = @Right(@Value(fme_feature_type),1)
    -> Junction_6
Junction_3
    -> Junction_5
    -> AttributeCreator_8
    -> deckline
    -> Scaler_2
Junction_5 [off]
deckline: Inspector
AttributeCreator_8
    ATTR_TABLE = SET_TO _order = 7
    -> Junction_6
Junction_6
    -> CoordinateExtractor_2
    -> CoordinateExtractor
CoordinateExtractor
    IND = 0
    MODE = Specify Coordinate
    X_ATTR = _x
    Y_ATTR = _y
    Z_ATTR = _z
    -> AttributeCreator_13
AttributeCreator_13
    ATTR_TABLE = SET_TO frame = s0
    -> VertexCreator
CoordinateExtractor_2
    IND = -1
    MODE = Specify Coordinate
    X_ATTR = _x
    Y_ATTR = _y
    Z_ATTR = _z
    -> AttributeCreator_12
AttributeCreator_12
    ATTR_TABLE = SET_TO frame = s99
    -> VertexCreator
VertexCreator
    MEASURE_TYPE = Continuous
    MODE_NAME = Replace with Point
    XVAL = @Value(_x)
    YVAL = @Value(_y)
    ZVAL = @Value(_z)
    -> Sorter
AttributeFilter_model: Logger
    LOG_FEATURE = LOG_ONLY
    MAXCOORDS = 20
    MAXFEATS = 20
    MESSAGE = Feature is:
    SEVERITY = INFO
AttributeFilter__Unfiltered_: Logger
    LOG_FEATURE = LOG_ONLY
    MAXCOORDS = 20
    MAXFEATS = 20
    MESSAGE = Feature is:
    SEVERITY = INFO
AttributeExposer_2
    ATTR_LIST = frame,kind,view
    -> AttributeFilter_2
AttributeFilter_2
    ATTR_NAME = kind
    ATTR_VALUES = <Empty>,<Missing>,<Null>,<Unfiltered>,diagonal,deckline
    diagonal -> AttributeExposer_3
    deckline -> AttributeCreator_11
AttributeExposer_3
    ATTR_LIST = angle,z0
    -> 3DRotator_2
3DRotator_2
    ANGLE = -@radToDeg(@Value(angle))
    AXIS_CHOICE = Custom Axis
    XDIR = 1
    XORIG = 0
    YDIR = 0
    YORIG = 0
    ZDIR = 0
    ZORIG = @Value(z0)
    ROTATED -> AttributeCreator_10
AttributeCreator_10
    ATTR_TABLE = SET_TO _order = @Right(@Value(diagonal),1)
    -> Sorter
AttributeCreator_11
    ATTR_TABLE = SET_TO _order = 7
    -> Sorter
Sorter
    SORT_PARM = frame ALPHA ASCENDING _order NUMERIC ASCENDING
    SORTED -> LineBuilder
LineBuilder
    ACCUM_INPUT_ATTRS = Drop Incoming Attributes
    GROUP_BY = frame
    REMOVE_DUPLICATES = No
    LINE -> CoordinateConcatenator
CoordinateConcatenator
    COORDINATES_TO_INCLUDE_DIS = X
    COORD_ATTR = autocad_fit_x
    COORD_DELIM = ,
    -> CoordinateConcatenator_2
CoordinateConcatenator_2
    COORDINATES_TO_INCLUDE_DIS = Y
    COORD_ATTR = autocad_fit_y
    COORD_DELIM = ,
    -> AttributeCreator_14
AttributeCreator_14
    ATTR_TABLE = SET_TO autocad_entity = autocad_spline
    -> FeatureWriter [Output]
FeatureWriter
    ACAD_APPEND_TO_TEMPLATEFILE = no
    ACAD_AUDIT_AND_FIX = yes
    ACAD_COORDINATE_SYSTEM_STORAGE = NONE
    ACAD_DEFAULT_ATTR_STORAGE = external_attributes
    ACAD_DESTINATION_DATASETTYPE_VALIDATION = Yes
    ACAD_OUTPUT_DEFINED_ATTRS_ONLY = yes
    ACAD_PREFER_DONUTS_AS_HATCHES = no
    ACAD_PRESERVE_TEMPLATE_PAPER_SPACE_ENTITIES = yes
    ACAD_PURGE = no
    ACAD_USE_BLOCK_NAME_FOR_CREATION = no
    ACAD_VERSION = Release2013
    ACAD_WRITE_THUMBNAIL_IMAGE = no
    DATASET = $(FME_MF_DIR_ENCODED)test_fit_pts.dxf
    DATASET_ATTR = _dataset
    FEATURE_TYPE_LIST_ATTR = _feature_type
    FORMAT = ACAD
    TOTAL_FEATURES_WRITTEN_ATTR = _total_features_written
    SUMMARY -> FeatureReader [INITIATOR]
FeatureReader
    ACAD_ALLOW_DASH_CHAR_IN_ATTR_NAMES = yes
    ACAD_ALL_MERGED_FILTERS_NEED_NO_DEFS = Yes
    ACAD_APPLY_WORLD_FILE = yes
    ACAD_CONVERT_ZERO_LENGTH_ARCS_TO_POINTS = yes
    ACAD_EVALUATE_MLINE_GEOM = no
    ACAD_EXPLODE_MTEXT = yes
    ACAD_IGNORE_FROZEN_LAYERS = no
    ACAD_IGNORE_HIDDEN_LAYERS = yes
    ACAD_IGNORE_UCS = no
    ACAD_INTERPRET_EXTENDED_DATA = yes
    ACAD_LIST_ATTRIBUTE_ENTITY_DATA = yes
    ACAD_LIST_EXTENDED_DATA = yes
    ACAD_METAFILE = acad
    ACAD_PRESERVE_CLIPPED_RASTERS = no
    ACAD_PRESERVE_COMPLEX_HATCHES = no
    ACAD_PRESERVE_INSERTS = no
    ACAD_QUERY_FEATURE_TYPES_FOR_MERGE_FILTERS = Yes
    ACAD_READ_AS_2_5D = no
    ACAD_READ_GROUPS = no
    ACAD_READ_MODEL_SPACE = yes
    ACAD_READ_PAPER_SPACE = NO
    ACAD_READ_PROXY_GRAPHICS = yes
    ACAD_READ_RASTERS = yes
    ACAD_READ_REGIONS_AS_AREAS = yes
    ACAD_READ_SYS_VARS = no
    ACAD_READ_USER_DICTIONARIES = no
    ACAD_READ_XREFS = no
    ACAD_RESOLVE_BLOCKS = yes
    ACAD_RESOLVE_DIMENSIONS = yes
    ACAD_RESOLVE_ENTITY_COLOR = yes
    ACAD_STORE_BULGE_INFO = no
    ACAD_STORE_INSERT_POINT = no
    ACAD_STORE_LAYER_INFO = no
    ACAD_STORE_SPLINE_DEFS = yes
    ACAD_STRUCTURE_EXTENDED_DATA = no
    ACAD_USE_BLOCK_HEADER_LAYER = yes
    ACAD_USE_BLOCK_LAYER_INFO = no
    ACAD_USE_SEARCH_ENVELOPE = NO
    ACAD_VISIBLE_ATTRIBUTES_AS_TEXT = yes
    ACAD_XRECORD_READING = None
    ATTR_ACCUM_MODE = Only Use Result
    COMBINE_GEOM = Use Result
    DATASET = $(FME_MF_DIR_ENCODED)test_fit_pts.dxf
    FORMAT = ACAD
    INTERACT = <No Spatial Filter>
    OUTPUT_FEATURES_DISPLAY = Schema and Data Features
    <OTHER> -> FeatureReader__Generic_
    <OTHER> -> Scaler_2
Scaler_2
    RASTER_SCALING = Extents
    SCALE_ORIGIN = 0,0
    TEXT_LOC_ONLY = Location and Size
    XSCALE = 1
    YSCALE = -1
    ZSCALE = 1
    SCALED -> Scaler_2_Scaled
Scaler_2_Scaled: Inspector
FeatureReader__Generic_: Inspector

Bookmark: Exctract fit points from intersection frame/spline
TestFilter
    DEFAULT_VALUE = <UNFILTERED>
    TEST_LIST:
      "BOOL_OP,AND,COMPOSITE_TEST,""""""1 AND 2"""""",TEST_CLAUSE,CASE_SENSITIVE_TEST @Value(fme_feature_type) CONTAINS_REGEX ^d\d$
      TEST @Value(autocad_entity) = autocad_spline",diagonal_spline,"BOOL_OP,AND,COMPOSITE_TEST,""""""1 AND 2"""""",TEST_CLAUSE,CASE_SENSITIVE_TEST @Value(fme_feature_type) CONTAINS_REGEX ^s\d$
      TEST @Value(autocad_entity) = autocad_line",frame_offset,"BOOL_OP,AND,COMPOSITE_TEST,""""""1 AND 2"""""",TEST_CLAUSE,CASE_SENSITIVE_TEST @Value(fme_feature_type) = dl_top_down
      TEST @Value(autocad_entity) = autocad_spline",deckline_spline,"BOOL_OP,AND,COMPOSITE_TEST,""""""1 AND 2"""""",TEST_CLAUSE,CASE_SENSITIVE_TEST @Value(fme_feature_type) = dl_sb_to_bb
      TEST @Value(autocad_entity) = autocad_spline",deckline_spline_sb_to_bb
    diagonal_spline -> AttributeCreator_2
    frame_offset -> AttributeCreator
    deckline_spline -> AttributeCreator_4
    deckline_spline_sb_to_bb -> AttributeCreator_5
AttributeCreator_2
    ATTR_TABLE = SET_TO diagonal = @Value(fme_feature_type)
    -> LineOnLineOverlayer [LINE]
AttributeCreator
    ATTR_TABLE = SET_TO frame = @Value(fme_feature_type)
    -> LineOnLineOverlayer [LINE]
    -> LineOnLineOverlayer_2 [LINE]
LineOnLineOverlayer
    ATTRS_ACCUM_MODE = Merge Attributes
    CLEANING_TOLERANCE = Automatic
    DEAGGREGATE_INPUT = Yes
    GENERATE_LIST_DROP = NO
    OV_ATTR = _overlaps
    SEPARATE_COLLINEAR_SEGMENTS = No
    POINT -> AttributeCreator_3
AttributeCreator_3
    ATTR_TABLE:
      SET_TO fme_feature_type = diagonal_fit_point
      SET_TO autocad_entity = autocad_point
      SET_TO view = 3
    -> Junction_2
AttributeCreator_4
    ATTR_TABLE = SET_TO view = 2
    -> LineOnLineOverlayer_2 [LINE]
AttributeCreator_5
    ATTR_TABLE = SET_TO view = 1
    -> LineOnLineOverlayer_2 [LINE]
LineOnLineOverlayer_2
    ATTRS_ACCUM_MODE = Merge Attributes
    CLEANING_TOLERANCE = Automatic
    DEAGGREGATE_INPUT = Yes
    GENERATE_LIST_DROP = NO
    OV_ATTR = _overlaps
    SEPARATE_COLLINEAR_SEGMENTS = No
    POINT -> AttributeCreator_6
AttributeCreator_6
    ATTR_TABLE:
      SET_TO fme_feature_type = deckline_fit_point
      SET_TO autocad_entity = autocad_point
    -> Junction_2
Junction_2
    -> Junction

Bookmark: axes
Creator
    COORDS = 0 0 0 1 0 0
    GEOMTYPE = 3D Coordinate List
    NUM = 1
    CREATED -> FeatureColorSetter
FeatureColorSetter
    COLOR = 1,0,0
    MODE = Fixed
    COLORED -> Scaler
Creator_2
    COORDS = 0 0 0 0 1 0
    GEOMTYPE = 3D Coordinate List
    NUM = 1
    CREATED -> FeatureColorSetter_2
FeatureColorSetter_2
    COLOR = 0,1,0
    MODE = Fixed
    COLORED -> Scaler
Creator_3
    GEOM = <?xml version="1.0" encoding="US_ASCII" standalone="no" ?><geometry><line><coord x="0" y="0" z="0"/><coord x="0" y="0" z="1"/></line></geometry>
    GEOMTYPE = Geometry Object
    NUM = 1
    CREATED -> FeatureColorSetter_3
FeatureColorSetter_3
    COLOR = 0,0,1
    MODE = Fixed
    COLORED -> Scaler
Scaler
    RASTER_SCALING = Extents
    SCALE_ORIGIN = 0,0
    TEXT_LOC_ONLY = Location and Size
    XSCALE = 100
    YSCALE = 100
    ZSCALE = 100
    SCALED -> axes
Note: 3D-rotation of diagonal control points is applied here because it's easier to use the 3DRotator compared to compute all the affine parameters in python. In order to complete the diagonals, they are stroked using python.
axes: Inspector
