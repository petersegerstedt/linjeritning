FME workspace convert_fit_pots_to_ctrl_pts.fmw

Creator
    COORDS = 0 0 1 0 1.5 0.5 2 0.25 3 -1
    GEOMTYPE = 2D Coordinate List
    NUM = 1
    CREATED -> CoordinateConcatenator
CoordinateConcatenator
    COORDINATES_TO_INCLUDE_DIS = X
    COORD_ATTR = autocad_fit_x
    COORD_DELIM = ,
    -> CoordinateConcatenator_2
CoordinateConcatenator_2
    COORDINATES_TO_INCLUDE_DIS = Y
    COORD_ATTR = autocad_fit_y
    COORD_DELIM = ,
    -> AttributeCreator
AttributeCreator
    ATTR_TABLE = SET_TO autocad_entity = autocad_spline
    -> FeatureWriter [Output]
FeatureWriter
    ACAD_APPEND_TO_TEMPLATEFILE = no
    ACAD_AUDIT_AND_FIX = yes
    ACAD_COORDINATE_SYSTEM_STORAGE = NONE
    ACAD_DEFAULT_ATTR_STORAGE = external_attributes
    ACAD_DESTINATION_DATASETTYPE_VALIDATION = Yes
    ACAD_OUTPUT_DEFINED_ATTRS_ONLY = yes
    ACAD_PREFER_DONUTS_AS_HATCHES = no
    ACAD_PRESERVE_TEMPLATE_PAPER_SPACE_ENTITIES = yes
    ACAD_PURGE = no
    ACAD_USE_BLOCK_NAME_FOR_CREATION = no
    ACAD_VERSION = Release2013
    ACAD_WRITE_THUMBNAIL_IMAGE = no
    DATASET = $(FME_MF_DIR_ENCODED)test_fit_pts.dxf
    DATASET_ATTR = _dataset
    FEATURE_TYPE_LIST_ATTR = _feature_type
    FORMAT = ACAD
    TOTAL_FEATURES_WRITTEN_ATTR = _total_features_written
    SUMMARY -> FeatureReader [INITIATOR]
FeatureReader
    ACAD_ALLOW_DASH_CHAR_IN_ATTR_NAMES = yes
    ACAD_ALL_MERGED_FILTERS_NEED_NO_DEFS = Yes
    ACAD_APPLY_WORLD_FILE = yes
    ACAD_CONVERT_ZERO_LENGTH_ARCS_TO_POINTS = yes
    ACAD_EVALUATE_MLINE_GEOM = no
    ACAD_EXPLODE_MTEXT = yes
    ACAD_IGNORE_FROZEN_LAYERS = no
    ACAD_IGNORE_HIDDEN_LAYERS = yes
    ACAD_IGNORE_UCS = no
    ACAD_INTERPRET_EXTENDED_DATA = yes
    ACAD_LIST_ATTRIBUTE_ENTITY_DATA = yes
    ACAD_LIST_EXTENDED_DATA = yes
    ACAD_METAFILE = acad
    ACAD_PRESERVE_CLIPPED_RASTERS = no
    ACAD_PRESERVE_COMPLEX_HATCHES = no
    ACAD_PRESERVE_INSERTS = no
    ACAD_QUERY_FEATURE_TYPES_FOR_MERGE_FILTERS = Yes
    ACAD_READ_AS_2_5D = no
    ACAD_READ_GROUPS = no
    ACAD_READ_MODEL_SPACE = yes
    ACAD_READ_PAPER_SPACE = NO
    ACAD_READ_PROXY_GRAPHICS = yes
    ACAD_READ_RASTERS = yes
    ACAD_READ_REGIONS_AS_AREAS = yes
    ACAD_READ_SYS_VARS = no
    ACAD_READ_USER_DICTIONARIES = no
    ACAD_READ_XREFS = no
    ACAD_RESOLVE_BLOCKS = yes
    ACAD_RESOLVE_DIMENSIONS = yes
    ACAD_RESOLVE_ENTITY_COLOR = yes
    ACAD_STORE_BULGE_INFO = no
    ACAD_STORE_INSERT_POINT = no
    ACAD_STORE_LAYER_INFO = no
    ACAD_STORE_SPLINE_DEFS = yes
    ACAD_STRUCTURE_EXTENDED_DATA = no
    ACAD_USE_BLOCK_HEADER_LAYER = yes
    ACAD_USE_BLOCK_LAYER_INFO = no
    ACAD_USE_SEARCH_ENVELOPE = NO
    ACAD_VISIBLE_ATTRIBUTES_AS_TEXT = yes
    ACAD_XRECORD_READING = None
    ATTR_ACCUM_MODE = Only Use Result
    COMBINE_GEOM = Use Result
    DATASET = $(FME_MF_DIR_ENCODED)test_fit_pts.dxf
    FORMAT = ACAD
    INTERACT = <No Spatial Filter>
    OUTPUT_FEATURES_DISPLAY = Schema and Data Features
    <OTHER> -> AttributeExposer
AttributeExposer
    ATTR_LIST = autocad_control_x,autocad_control_y,autocad_fit_x,autocad_fit_y,fme_feature_type
    -> FeatureReader__Generic_
    -> PythonCaller
FeatureReader__Generic_: Inspector [off]
PythonCaller
    PYTHONSOURCE:
      import fmeobjects

      class FeatureProcessor(object):
          def __init__(self):
              pass
          def input(self,feature):
              ctrl_pts = zip(*[list(map(float, feature.getAttribute('autocad_control_{}'.format(s)).split(','))) for s in ('x','y')])
              for  x, y in ctrl_pts:
                  p = feature.clone()
                  p.setGeometry(fmeobjects.FMEPoint(x,y))
                  p.setAttribute('fme_feature_type', 'control_points')
                  self.pyoutput(p)
              fit_pts = zip(*[list(map(float, feature.getAttribute('autocad_fit_{}'.format(s)).split(','))) for s in ('x','y')])
              for  x, y in fit_pts:
                  p = feature.clone()
                  p.setGeometry(fmeobjects.FMEPoint(x,y))
                  p.setAttribute('fme_feature_type', 'fit_points')
                  self.pyoutput(p)
              self.pyoutput(feature)
          def close(self):
              pass
    PYTHONSYMBOL = FeatureProcessor
    -> PythonCaller_Output_Logged
PythonCaller_Output_Logged: Inspector
    TACKATTRS = fme_feature_type
